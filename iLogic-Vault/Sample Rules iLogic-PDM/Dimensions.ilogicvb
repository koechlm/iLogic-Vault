'DISCLAIMER:
'---------------------------------
'In any case, code, templates, and snippets of this solution are of "work in progress" character.
'Neither Markus Koechl, nor Autodesk represents that these samples are reliable, accurate, complete, or otherwise valid. 
'Accordingly, those configuration samples are provided “as is” with no warranty of any kind and you use the applications at your own risk.

Sub Main
	'the rule must not run on any file, e.g. library files usually down't alllow changes or vaulted files not checked out.
	If mCheckLibraries  = True Then Exit Sub 'the rule can't add properties/values to content center or library files	
	If mFileReadOnly = True Then Exit Sub 'the rule can't apply changes if the file is write protected
	
	Dim oDoc As Inventor.Document
	Dim oPartDoc As Inventor.PartDocument
	Dim oCompDef As Inventor.ComponentDefinition

	Dim oFlatExtent As Boolean = False
	Try
		mFileInfo = New System.IO.FileInfo(ThisDoc.Document.FullFileName)
		If mFileInfo.IsReadOnly = False Then
			Logger.Info("File " & ThisDoc.FileName & "  is Write Enabled")
		Else
			Logger.Warn("File " & ThisDoc.FileName & " is ReadOnly; rule 'Dimensions' stops execution.")
			Exit Sub
		End If
		oDoc = ThisDoc.Document
		'set the length units string
		Units = oDoc.UnitsOfMeasure.LengthUnits
		Select Case Units
		Case 11269
			UnitString = "mm"
		Case 11268
			UnitString = "cm"
		Case 11270
			UnitString = "m"
		Case 11272
			UnitString = "in"
		Case 11273
			UnitString = "ft"
		End Select

		If oDoc.DocumentType = kPartDocumentObject Then
		    oPartDoc = oDoc
			If oPartDoc.SubType = "{9C464203-9BAE-11D3-8BAD-0060B0CE6BB4}" Then 'sheet metal part
					oCompDef = oPartDoc.ComponentDefinition
					If oCompDef.HasFlatPattern = True Then
						oFlatExtent = True
					End If
					If oFlatExtent = False Then
						L = Round(Measure.ExtentsLength,1)
						W = Round(Measure.ExtentsWidth, 1)
						H = Round(Measure.ExtentsHeight, 1)
						iProperties.Value("Custom", "Dimensions") = W & "x" & H & "x" & L & " " & UnitString
						Exit Sub
					Else 'no flat pattern
						L = Round(SheetMetal.FlatExtentsLength, 1)
						W = Round(SheetMetal.FlatExtentsWidth, 1)
						iProperties.Value("Custom", "G_L") = W & "x" & L & " " & UnitString
						iProperties.Value("Custom", "Thickness") = oCompDef.Thickness.Expression
						'cross section unfolded model
						L = Round(Measure.ExtentsLength,1)
						W = Round(Measure.ExtentsWidth, 1)
						H = Round(Measure.ExtentsHeight, 1)
						iProperties.Value("Custom", "Dimensions") = W & "x" & H & "x" & L & " " & UnitString
						Exit Sub
					End If 'flat pattern
			End If 'sheet metal part
			
			'check that default parameters beside G_L are used
			'round bars, shafts
			Try
				If (Parameter("G_D") <> 0 And Parameter("G_L") <> 0) Then
					Dia = Round(Parameter("G_D"), 1)
					L = Round(Parameter("G_L"),1)
					iProperties.Value("Custom", "Dimensions") = Dia & "x" & L & " " & UnitString
					Exit Sub
				End If
		Catch
			Logger.Info("Could not retrieve parameters for round bar dimensions")	
		End Try
		'other square or rectangle shaped components
		Try
			If (Parameter("G_W") <> 0 And Parameter("G_H") And Parameter("G_L") <> 0) Then
				W = Round(Parameter("G_W"), 1)
				H = Round(Parameter("G_H"), 1)
				L = Round(Parameter("G_L"),1)
				iProperties.Value("Custom", "Dimensions") = W & "x" & H & "x" & L & " " & UnitString
				Exit Sub
			End If
	Catch
			Logger.Info("Could not retrieve parameters for square/rectangle bar dimensions")	
	End Try
	End If 'part document

	'all others and assembly documents
	L = Round(Measure.ExtentsLength,1)
	W = Round(Measure.ExtentsWidth, 1)
	H = Round(Measure.ExtentsHeight, 1)
	iProperties.Value("Custom", "Dimensions") = W & "x" & H & "x" & L & " " & UnitString

	Catch ex As Exception
		Logger.Error("Error retrieving Custom Parameter 'Dimensions'!")
	End Try

End Sub

'function to validate that current file is not a Content Center or user Library file
Function mCheckLibraries() As Boolean
	
	Dim mDirInfo As System.IO.DirectoryInfo
	Dim mLibPath As Inventor.ProjectPath
	Dim mTmpPath As String
	Dim mCCPath As String 
	Dim mIPJ As Inventor.DesignProject
	Dim mIpjPath As String
	
	If (ThisDoc.Document.FileSaveCounter <> 0) Then
		Try
			mCCPath = ThisApplication.DesignProjectManager.ActiveDesignProject.ContentCenterPath
			mIPJ = ThisApplication.DesignProjectManager.ActiveDesignProject
			mIpjPath = mIPJ.FullFileName
			mFileInfo = New System.IO.FileInfo(ThisDoc.Document.FullFileName)
			If InStr(mFileInfo.FullName, mCCPath.ToString) Then Return True
			For Each mLibPath In mIPJ.LibraryPaths
			    'check relative/absolute paths
			    If mLibPath.Path.StartsWith(".\") Then
			        mDirInfo = New System.IO.DirectoryInfo(mIPJ.FullFileName)
			        mTmpPath = mDirInfo.Root.ToString & mDirInfo.Parent.ToString & mLibPath.Path.ToString.Replace(".\", "\")
			    End If
			    If mFileInfo.FullName.StartsWith(mTmpPath) Then Return True
			Next
		Catch
			Logger.Error("Error in Function mCheckLibraries.")
		End Try
	Else
		Logger.Info("File is not saved yet; readonly check skipped.")
	End If
End Function

'Function to validate that the current file is editable.
Function mFileReadOnly As Boolean
	Dim mFileInfo As System.IO.FileInfo
	'for new document, not saved yet the readonly check is not required
	If (ThisDoc.Document.FileSaveCounter <> 0) Then
	mFileInfo = New System.IO.FileInfo(ThisDoc.Document.FullFileName)	
		Logger.Info(mFileInfo.DirectoryName)
		If mFileInfo.IsReadOnly = False Then
			Logger.Info("File " & ThisDoc.FileName & "  is Write Enabled")
			Return False
		Else
			Logger.Warn("File " & ThisDoc.FileName & " is ReadOnly; rule " & " stops execution.")
			Return True
		End If
	Else
		Logger.Info("File is not saved yet; readonly check skipped.")
	End If
End Function
