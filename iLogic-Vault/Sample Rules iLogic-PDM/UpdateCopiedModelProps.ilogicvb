'DISCLAIMER:
'---------------------------------
'In any case, code, templates, and snippets of this solution are of "work in progress" character.
'Neither Markus Koechl, nor Autodesk represents that these samples are reliable, accurate, complete, or otherwise valid. 
'Accordingly, those configuration samples are provided “as is” with no warranty of any kind and you use the applications at your own risk.

Sub Main
	Dim oApp As Inventor.Application = ThisApplication
	Try
		'If oApp.ActiveDocumentType = DocumentTypeEnum.kDrawingDocumentObject Then oDrawDoc = oApp.ActiveDocument
		Dim oControlDef As Inventor.ControlDefinition
		oControlDef = oApp.CommandManager.ControlDefinitions.Item("UpdateCopiedModeliPropertiesCmd")
		oControlDef.Execute2(True)
	Catch
		Logger.Error("Rule 'UpdateCopiedModelProps failed.' ")
	End Try
End Sub
