AddReference "System.Drawing"
'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If
	
	Dim mImage As System.Drawing.Image = iLogicVault.GetThumbnailImageByFullSourceFilePath("$/Designs/Inventor Sample Data/Fishing Rod/Back Side Cover.ipt", 254, 254)
	If mImage Is Nothing Then
		Logger.Error("Could not convert thumbnail to image file - Please double check that file exists in Vault including a thumbnail.")
	Else
		Logger.Info("Successfully downloaded thumbnail as image object; as of today, the consumption of Image objects is for custom dialogs (dll) only.")

	End If

End Sub
