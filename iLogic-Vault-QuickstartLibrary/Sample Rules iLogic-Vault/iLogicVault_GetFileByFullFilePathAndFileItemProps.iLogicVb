'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If

	'returns full file name in local working folder (download enforces override, if local file exists); hand over an empty dictionary for properties
	Dim mVaultFileProps As System.Collections.Generic.Dictionary(Of String, String) = New Dictionary(Of String, String)
	Dim mVaultItemProps As System.Collections.Generic.Dictionary(Of String, String) = New Dictionary(Of String, String)
	Dim mVaultFile As String = iLogicVault.GetFileByFullFilePath("$/Designs/Inventor Sample Data/Fishing Rod/Back Side Cover.ipt", mVaultFileProps, mVaultItemProps) 'Optionally add ..., True) to activate check out for the file downloaded.
	If mVaultFile Is Nothing Then
		Logger.Error("Vault file not found. Please double check that file path is correct or that the file exists in Vault.")
	Else
		Logger.Info("File " & mVaultFile & " (including dependent and attachment files) downloaded.")
		For Each item In mVaultFileProps
			Logger.Info("Vault File Property Name/Value: " + item.Key + " = " + item.Value)
		Next
		For Each item In mVaultItemProps
			Logger.Info("Vault linked Item Property Name/Value: " + item.Key + " = " + item.Value)
		Next
		Logger.Info("File " & mVaultFile & " download finished.")
		'add next action using the downloaded file here, e.g. Component.Replace("Part1:1", mVaultFile, True)
	End If

End Sub
