AddReference "QuickstartiLogicLibrary.dll"
AddReference "Autodesk.Connectivity.WebServices.dll"
Imports AWS = Autodesk.Connectivity.WebServices
AddReference "Autodesk.DataManagement.Client.Framework.Vault.dll"
Imports VDF = Autodesk.DataManagement.Client.Framework
Sub Main
'Sample based on Vault "INV-Samples" available; adopt search criteria below according other Vault's content.

	Dim iLogicVault As New QuickstartiLogicLibrary.QuickstartiLogicLib 'Note - Header "Vault Header" required; insert from iLogic-Vault Quickstart Library
	Dim mVltCon As VDF.Vault.Currency.Connections.Connection 'Note - Header "Vault Header" required; insert from iLogic-Vault Quickstart Library

	mVltCon = iLogicVault.mGetVaultConn()
	If  mVltCon Is Nothing Then
		Logger.Error("Not Logged In to Vault! - Login first and repeat executing this rule.")
		Exit Sub
	ElseIf mVltCon.IsConnected = True Then
		Logger.Info("Validated Vault Connection: Connected")
		'Build one to many name/value pairs of Property/Value as search criteria;
		Dim mSearchParams As New System.Collections.Generic.Dictionary(Of String, String) 'add UDP.DisplayName, Value Pairs
		mSearchParams.Add("Part Number", "001003")		'applies to file 001003.ipt
		mSearchParams.Add("Title", "Back Side Cover") 	'applies to file 001002.ipt and to file 001068.iam
		'...add as many as required to enable a unique search result
		
		Dim mVaultFiles As String()
		mVaultFiles = iLogicVault.mCheckFilesExistBySearchCriteria(mVltCon, mSearchParams, False)
		'returns full file name in local working folder (download enforces override, if local file exists)
		'returns "FileNotFound if file does not exist at indicated location
		If mVaultFiles.Count = 0 Then
			MessageBox.Show("The file searched was not found" & vbCr & "Please double check that file can be found with search criteria applied." , "Quickstart iLogic Library", MessageBoxButtons.OK)
		ElseIf mVaultFiles.Count > 0 Then
			Dim mFileList As String
			For Each mFile As String In mVaultFiles
				mFileList += mFile & vbCr
			Next
			MessageBox.Show("iLogic-Vault file search found: " & vbCr & mFileList, "Quickstart iLogic Library", MessageBoxButtons.OK)
		End If
	End If

End Sub
