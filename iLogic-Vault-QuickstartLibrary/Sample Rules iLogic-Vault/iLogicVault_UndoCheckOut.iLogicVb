'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state
	If iLogicVault.LoggedIn = False
		Logger.Error("Not Logged In to Vault! - Login first and repeat executing this rule.")
		Exit Sub
	End If

	Try
		Dim oApp As Inventor.Application = ThisApplication
		Dim oControlDef As Inventor.ControlDefinition
		oControlDef = ThisApplication.CommandManager.ControlDefinitions.Item("VaultUndoCheckoutTop")
		oControlDef.Execute2(True)
	Catch
	End Try

End Sub
