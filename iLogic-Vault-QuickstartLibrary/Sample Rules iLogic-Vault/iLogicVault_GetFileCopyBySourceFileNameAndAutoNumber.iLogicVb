'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If
	
	'Set the name of the numbering scheme or use 'Default' to use the pre-set scheme
	Dim mNumSchmName As String = "Default"
	'Optionally collect input values for file the selected numbering scheme; use the order of the fields as configured in the scheme;
	Dim mNumInput As New System.Collections.Generic.List(Of String)

	'returns full file name in local working folder (download enforces override, if local file exists)
	Dim mVaultFile As String = iLogicVault.GetFileCopyBySourceFileNameAndAutoNumber("$/Designs/Inventor Sample Data/Fishing Rod/Back Side Cover.ipt", mNumSchmName, , False) 'optionally add the mNumInput variable; note - the check-out flag is an option also; default = True.
	If mVaultFile Is Nothing Then
		Logger.Error("File copy not created; check that the file can get found; does Vault provide a 'Default' numbering scheme?" )
	Else
		Logger.Info("File " & mVaultFile & " created As copy.")
			'add next action using the downloaded file here, e.g. Component.Replace("Part1:1", mVaultFile, True)
	End If
	
End Sub
