'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If
	
	'Build one to many name/value pairs of Property/Value as search criteria;
	Dim mSearchParams As New System.Collections.Generic.Dictionary(Of String, String) 'add UDP.DisplayName, Value Pairs
	mSearchParams.Add("Part Number", "403-0*") 'applies to files with part numbers 403-01 ... 403-09
	'...add as many as required to enable a unique search result
	
	'the list of downloaded files
	Dim mVaultFiles As List(Of String)
	'returns full file names in local working folder (download enforces override, if local file exists)
	'returns null (nothing) if no files return		
	mVaultFiles = iLogicVault.GetFilesBySearchCriteria(mSearchParams, False, False)  'the default for optional parameter MatchAllCriteria = false, CheckOut = true, searching all folders
	'prepare output
	If mVaultFiles.Count = 0 Then
		Logger.Error("The file searched was not found. Please double check that files can be found with search criteria applied.")
	ElseIf mVaultFiles.Count > 0 Then
		mVaultFiles.Sort()
		Dim mFileList As String
		For Each mFile As String In mVaultFiles
			mFileList += vbCr & mFile 
		Next
		Logger.Info("iLogic-Vault file search found and downloaded (note: dependent and attachment files are included in the download, but not listed): " & mFileList)
		Logger.Info("Multiple file search and download finished.")
		'so the files are there, do what ever you need to do consuming these...
	End If

End Sub
