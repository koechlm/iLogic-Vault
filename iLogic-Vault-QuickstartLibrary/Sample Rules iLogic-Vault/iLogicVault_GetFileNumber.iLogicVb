AddReference "QuickstartiLogicLibrary.dll"
AddReference "Autodesk.Connectivity.WebServices.dll"
Imports AWS = Autodesk.Connectivity.WebServices
AddReference "Autodesk.DataManagement.Client.Framework.Vault.dll"
Imports VDF = Autodesk.DataManagement.Client.Framework
Sub Main
	
	'Sample based on Vault "INV-Samples" available; adopt search criteria or file path(s) below according other Vault's content.
	
	Dim iLogicVault As New QuickstartiLogicLibrary.QuickstartiLogicLib 
	Dim mVltCon As VDF.Vault.Currency.Connections.Connection
	mVltCon = iLogicVault.mGetVaultConn()
	If  mVltCon Is Nothing Then
		Logger.Error("Not Logged In to Vault! - Login first and repeat executing this rule.")
		Exit Sub
	ElseIf mVltCon.IsConnected = True Then
		'MessageBox.Show("Logged In to Vault", "Quickstart iLogic Library", MessageBoxButtons.OK)
	End If
	
	'Optionally collect input values for file the selected numbering scheme; use the order of the fields as configured in the scheme;
	Dim mNumInput As New System.Collections.Generic.List(Of String) 'add UDP.DisplayName, Value Pairs
	
	'returns full file name in local working folder (download enforces override, if local file exists)
	'returns "FileNotFound if file does not exist at indicated location
	Dim mNumSchmName As String = "Default" 'change the name, if other scheme than the configured default should create the number
	Dim mFileNumber As String = iLogicVault.mGetNewNumber(mVltCon, mNumSchmName) 'optionally add the mNumInput variable
	If mFileNumber = "GetNumberFailed" Then
		Logger.Error("Number generation failed; check name (if not 'Default') or input parameters if required.")
	Else
		Logger.Info("File Number " & mFileNumber & " created and ready for consumption.")
			'add next action using the downloaded file here, e.g. Component.Replace("Part1:1", mLocalFileCopy, True)
		Dim mFullFileName As String = ThisDoc.Document.FullFileName
        'ThisDoc.Document.SaveAs(mFileNumber, True)
		Dim mLocaFileCopy As String = iLogicVault.mCopyLocalFile(mFullFileName, mFileNumber)

	End If
	
End Sub
