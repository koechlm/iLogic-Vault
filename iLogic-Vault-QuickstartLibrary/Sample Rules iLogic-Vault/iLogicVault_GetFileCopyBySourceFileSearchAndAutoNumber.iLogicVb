'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If	
	
	'Build one to many name/value pairs of Property/Value as search criteria;
	Dim mSearchParams As New System.Collections.Generic.Dictionary(Of String, String) 'add UDP.DisplayName, Value Pairs
	mSearchParams.Add("Part Number", "407-02")	'applies to the file $\Designs\Inventor Sample Data\Fishing Rod\Back Side Cover.ipt
	'...add as many as required to enable a unique search result
	
	'Set the name of the numbering scheme or use 'Default' to use the pre-set scheme
	Dim mNumSchmName As String = "Default"
	'Optionally collect input values for file the selected numbering scheme; use the order of the fields as configured in the scheme;
	Dim mNumInput As New System.Collections.Generic.List(Of String) 'add UDP.DisplayName, Value Pairs
	
	'returns full file name in local working folder (download enforces override, if local file exists)
	Dim mVaultFile As String = iLogicVault.GetFileCopyBySourceFileSearchAndAutoNumber(mSearchParams, mNumSchmName, True, , False, , True) 'the default for optional parameter MatchAllCriteria = false, CheckOut = true, and search in all folders starting from root $/
	If mVaultFile Is Nothing Then
		Logger.Error("File copy not created; verify that the file can be found by the search criteria applied. Also verify your input of numbering sheme name and optional parameters")
	Else
		Logger.Info("File " & mVaultFile & " created As New copy Of search result." )
			'add next action using the downloaded file here, e.g. Component.Replace("Part1:1", mVaultFile, True)
	End If
	
End Sub
