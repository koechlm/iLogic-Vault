'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If
	
	'Set the name of the numbering scheme or use 'Default' to use the pre-set scheme
	Dim mNumSchmName As String = "Default"
	'Optionally collect input values for file the selected numbering scheme; use the order of the fields as configured in the scheme;
	Dim mNumInput As New System.Collections.Generic.List(Of String) 'add UDP.DisplayName, Value Pairs

	'Create single file number by scheme name and optional input parameters; returns new number or error message "GetNumberFailed"
	Dim mFileNumber As String = iLogicVault.GetNewNumber(mNumSchmName) 'optionally add the mNumInput variable adding ...", mNumInput)
	If mFileNumber Is Nothing Then
		Logger.Error("Number generation failed; check name (if not 'Default') or input parameters if required.")
	Else
		Logger.Info("File Number " & mFileNumber & " created and ready for consumption.")
			'add next action using the downloaded file here, e.g. Component.Replace("Part1:1", mLocalFileCopy, True)
		Dim mFullFileName As String = ThisDoc.Document.FullFileName
        'ThisDoc.Document.SaveAs(mFileNumber, True)
		Dim mLocaFileCopy As String = iLogicVault.CopyLocalFile(mFullFileName, mFileNumber)
		Logger.Info("Copied current file consuming the new number " & mFileNumber)
	End If
	
End Sub
