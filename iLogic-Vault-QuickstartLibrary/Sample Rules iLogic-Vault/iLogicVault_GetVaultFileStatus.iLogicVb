'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If

	'Retrieve the active document's Vault file status as name/value pairs 
	Dim mDocVaultStatus As New Dictionary(Of String, String)
	mDocVaultStatus = iLogicVault.GetVaultFileStatus(ThisDoc.PathAndFileName(True))
	If mDocVaultStatus.Item("ErrorState") = "None" Then
		Logger.Info("CheckOutState = " + mDocVaultStatus.Item("CheckOutState"))
		Logger.Info("ConsumableState = " + mDocVaultStatus.Item("ConsumableState"))
		Logger.Info("ErrorState = " + mDocVaultStatus.Item("ErrorState"))
		Logger.Info("LocalEditsState = " + mDocVaultStatus.Item("LocalEditsState"))
		Logger.Info("LockState = " + mDocVaultStatus.Item("LockState"))
		Logger.Info("RevisionState = " + mDocVaultStatus.Item("RevisionState"))
		Logger.Info("VersionState = " + mDocVaultStatus.Item("VersionState"))
	Else
		Logger.Error("ErrorState = " + mDocVaultStatus.Item("ErrorState"))
	End If

End Sub
