AddReference "QuickstartiLogicLibrary.dll"
AddReference "Autodesk.Connectivity.WebServices.dll"
Imports AWS = Autodesk.Connectivity.WebServices
AddReference "Autodesk.DataManagement.Client.Framework.Vault.dll"
Imports VDF = Autodesk.DataManagement.Client.Framework
Sub Main
	Dim iLogicVault As New QuickstartiLogicLibrary.QuickstartiLogicLib 
	Dim mVltCon As VDF.Vault.Currency.Connections.Connection
	mVltCon = iLogicVault.mGetVaultConn()
	If  mVltCon Is Nothing Then
		MessageBox.Show("Not Logged In to Vault!" & vbCr & "Login first and repeat executing this rule." , "Quickstart iLogic Library", MessageBoxButtons.OK, MessageBoxIcon.Error)
		Exit Sub
	ElseIf mVltCon.IsConnected = True Then
		'MessageBox.Show("Logged In to Vault", "Quickstart iLogic Library", MessageBoxButtons.OK)
	End If
	
	'returns full file name in local working folder (download enforces override, if local file exists)
	'returns "FileNotFound if file does not exist at indicated location
	Dim mVaultFile As String = iLogicVault.mGetFileByFullFileName(mVltCon, "$/Designs.ipj")
	If mVaultFile = "FileNotFound" Then
		MessageBox.Show("Vault file not found" & vbCr & "Please double check that file exists in Vault." , "Quickstart iLogic Library", MessageBoxButtons.OK)
	ElseIf mVaultFile <> "FileNotFound" Then
			'add next action using the downloaded file here, e.g. Component.Replace("Part1:1", mVaultFile, True)
	End If
	
End Sub
