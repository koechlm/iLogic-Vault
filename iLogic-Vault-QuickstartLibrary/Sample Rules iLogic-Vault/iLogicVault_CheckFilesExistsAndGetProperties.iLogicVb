'DISCLAIMER:
'---------------------------------
'In any case, this solution's code, templates, and snippets are of "work in progress" character.
'Autodesk does Not represent that these samples are reliable, accurate, complete, Or otherwise valid For production usage. 
'Accordingly, those configuration samples are provided “as is” with no warranty of any kind, and you use the applications at your own risk.

Sub Main

	'Validate user's login state; it is optional as iLogicVault methods throw an exception with message 'Please log in to Vault before using this function'.
	If iLogicVault.LoggedIn = False
		Logger.Error("Not Logged In to Vault! - Login first and repeat executing this rule.")
		Exit Sub
	End If

	'Build one to many name/value pairs of Property/Value as search criteria;
	Dim mSearchParams As New Dictionary(Of String, String) 'add UDP.DisplayName, Value Pairs
	mSearchParams.Add("Part Number", "407-02")	'applies to the file $\Designs\Inventor Sample Data\Fishing Rod\Back Side Cover.ipt
	mSearchParams.Add("Name", "Back Side Cover*") 'applies to the files Back Side Cover.ipt and Back Side Cover.iam

	Dim mAllFilesProperties As System.Collections.Generic.Dictionary(Of String, Dictionary(Of String, String)) = New Dictionary(Of String, Dictionary(Of String, String))

	Dim mVaultFiles As List(Of String)
	mVaultFiles = iLogicVault.CheckFilesExistBySearchCriteria(mSearchParams, mAllFilesProperties, True)
	If mVaultFiles Is Nothing Then
		Logger.Error("The file(s) searched was(were) not found. Please double check that the search criteria's relevance.")
	ElseIf mVaultFiles.Count > 0 Then
		For Each mFile As String In mVaultFiles
			Logger.Info("iLogic-Vault file search found: " + mFile)
			Dim mPropValPairs As Dictionary(Of String, String) = mAllFilesProperties(mFile)
			For Each item In mPropValPairs
				Logger.Info(mFile + " Property DisplayName=Value: " + item.Key + "=" + item.Value)
			Next
		Next
	End If

End Sub
