AddReference "QuickstartiLogicLibrary.dll"
'DISCLAIMER:
'---------------------------------
'In any case, code, templates, and snippets of this solution are of "work in progress" character.
'Neither Markus Koechl, nor Autodesk represents that these samples are reliable, accurate, complete, or otherwise valid. 
'Accordingly, those configuration samples are provided “as is” with no warranty of any kind and you use the applications at your own risk.

Sub Main
	'Sample based on Vault "INV-Samples" available; adopt search criteria below according other Vault's content.
	'enable iLogicVault commands and validate user's login state
	Dim iLogicVault As New QuickstartiLogicLibrary.QuickstartiLogicLib
	If iLogicVault.LoggedIn = False
		Logger.Error("Not Logged In to Vault! - Login first and repeat executing this rule.")
		Exit Sub
	End If

	'Build one to many name/value pairs of Property/Value as search criteria;
	Dim mSearchParams As New Dictionary(Of String, String) 'add UDP.DisplayName, Value Pairs
	mSearchParams.Add("Part Number", "001002")	'applies to file 001002.ipt
	mSearchParams.Add("Title", "Back Side Cover*") 	'applies to file 001002.ipt and to file 001068.iam
	'...add as many as required to enable a unique search result

	Dim mAllFilesProperties As System.Collections.Generic.Dictionary(Of String, Dictionary(Of String, String)) = New Dictionary(Of String, Dictionary(Of String, String))

	Dim mVaultFiles As List(Of String)
	mVaultFiles = iLogicVault.CheckFilesExistBySearchCriteria(mSearchParams, mAllFilesProperties, True)
	If mVaultFiles Is Nothing Then
		Logger.Error("The file(s) searched was(were) not found. Please double check that the search criteria's relevance.")
	ElseIf mVaultFiles.Count > 0 Then
		For Each mFile As String In mVaultFiles
			Logger.Info("iLogic-Vault file search found: " + mFile)
			Dim mPropValPairs As Dictionary(Of String, String) = mAllFilesProperties(mFile)
			For Each item In mPropValPairs
				Logger.Info(mFile + " Property DisplayName=Value: " + item.Key + "=" + item.Value)
			Next
		Next
	End If

End Sub
