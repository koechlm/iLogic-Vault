AddReference "QuickstartiLogicVltInvSrvLibrary.dll"
AddReference "Autodesk.Connectivity.WebServices.dll"
AddReference "Autodesk.DataManagement.Client.Framework.Vault.dll"
'DISCLAIMER:
'---------------------------------
'In any case, code, templates, and snippets of this solution are of "work in progress" character.
'Neither Markus Koechl, nor Autodesk represents that these samples are reliable, accurate, complete, or otherwise valid. 
'Accordingly, those configuration samples are provided “as is” with no warranty of any kind and you use the applications at your own risk.

Sub main

	break 'use for step by step debugging in Visual Studio

	Dim ex As Exception 'the job processor host evaluates it in case

	Dim oDoc As AssemblyDocument
	oDoc = ThisDoc.Document
	If oDoc.DocumentType <> Inventor.DocumentTypeEnum.kAssemblyDocumentObject
		Logger.Error("This sample rule expects an assembly document.")
		Exit Sub
	End If

	' activate the Master model state if the active model state is substitute.
	If oDoc.ComponentDefinition.ModelStates.ActiveModelState.ModelStateType = ModelStateTypeEnum.kSubstituteModelStateType Then
		oDoc.ComponentDefinition.ModelStates.Item(1).Activate
		oDoc = ThisApplication.ActiveDocument
	End If

	'check existing export definition
	Dim oRevitExport As Inventor.RevitExport
	Dim oRevitExportDef As RevitExportDefinition
	Dim oNewExp As Boolean = False
	oExportFullName = ThisDoc.Path + "\" + ThisDoc.FileName(True).Replace(".iam", ".rvt")

	For Each item As RevitExport In oDoc.ComponentDefinition.RevitExports
		If item.FullFileName = oExportFullName Then
			oRevitExport = item
			oRevitExportDef = item.Definition
		End If
	Next

	'create new definition in case it does not exist
	If oRevitExportDef Is Nothing Then
		oNewExp = True
		oRevitExportDef = oDoc.ComponentDefinition.RevitExports.CreateDefinition
		'derive file name from source
		oRevitExportDef.Location = ThisDoc.Path
		oRevitExportDef.FileName = ThisDoc.FileName(True).Replace(".iam", ".rvt")
	End If

	'Set Revit Export options
	oRevitExportDef.Structure = kEachTopLevelComponentStructure
	oRevitExportDef.EnableUpdating = True
	'...there are more available; check Inventor API Help

	'clean local working folder; existing files in Vault update a new iteration
	success = mCleanWfFile(oExportFullName)
	If success = True Then

		' Create RevitExport or update the existing
		If oNewExp = True Then

			oRevitExport = oDoc.ComponentDefinition.RevitExports.Add(oRevitExportDef)

			If oRevitExport.FullFileName <> oExportFullName Then
				Logger.Error("Export of Revit file either failed, or the target file name did not match the definition.")
				Exit Sub
			End If
		Else
			oRevitExport.Update()
		End If

		'get the job processor's Vault connection (note - this is different from Inventor Application)
		Dim iLogicVault As New QuickstartiLogicVltInvSrvLibrary.iLogicVltInvSrvLibrary
		Dim LoggedIn As Boolean
		Dim FileState As String
		Try
			dbServer = RuleArguments("ServerName")
			fServer = RuleArguments("ServerName")
			vltName = RuleArguments("VaultName")
			userId = RuleArguments("UserId")
			SessionId = RuleArguments("SessionId")
			LoggedIn = iLogicVault.ReuseConnection(dbServer, fServer, vltName, userId, SessionId)
		Catch
			Logger.Error("Could not re-use the Job Processor's Vault connection; check the rule arguments.")
			Throw ex
		End Try

		'upload file as new or incremental file iteration
		Dim mVaultPath As String = iLogicVault.ConvertLocalPathToVaultPath(oRevitExport.FullFileName)
		success = iLogicVault.AddFile(oExportFullName, mVaultPath, True)
		If (success <> True)
			Logger.Error("Failed to add/update Revit file to Vault")
			Throw ex
		End If

	End If 'clean local working folder

End Sub

Private Function mCleanWfFile(mFile As String) As Boolean
	'Delete existing file to avoid overwrite restrictions
	Dim oFileInfo As New System.IO.FileInfo(mFile)
	Try
		If oFileInfo.Exists = True Then
			If (oFileInfo.Attributes) Then
				oFileInfo.Attributes = (oFileInfo.Attributes And Not oFileInfo.Attributes.ReadOnly)
				System.IO.File.Delete(mFile)
			End If
		End If
		Return True
	Catch
		Return False
	End Try
End Function
